# All features
Exported for the round trip test

# Specification: System Spec
- Owner: Team A

## REQ-1: Boot
First requirement
The system shall boot.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
- Count: 99999999999
- Effort: 2.5
- Safety: true
- Due: 2026-12-31T23:59:59+01:00
- Status: Done
- Tags: Open, Done

### REQ-2
A single paragraph.
- refines -> REQ-1
